module leaf-only-example {
    yang-version "1";
    namespace "urn:leaf-only-example";
    prefix re;
    identity routing-protocol;

    identity ospf {
        base routing-protocol;
    }

    identity bgp {
        base routing-protocol;
    }

    container A {
        leaf protocol {
            type identityref {
                base routing-protocol;
            }
        }
    }
}
